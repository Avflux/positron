; Rodada 183: roda em COPIA do Funcional.dwg. TextString difere do XData;
; mais de quatro entidades titulo e indice 9 provam o AtualizaTitulos da grade.
(regapp "DiagLog")
(defun pz-titulos:novo (indice texto /)
  (entmakex (list '(0 . "TEXT") '(8 . "2") '(10 950000.0 0.0 0.0) '(40 . 2.5)
    (cons 1 texto)
    (list -3 (list "DiagLog" '(1000 . "TituloPagina") (cons 1070 indice)
      '(1000 . "XDATA ANTIGO") '(1070 . 1) '(1000 . "harness") '(1000 . "183")
      '(1071 . 1) '(1040 . 1.0) '(1000 . " "))))))
(if (= (getenv "POSITRON_TITULOS_MONTAR") "1")
  (progn
    (repeat 5 (pz-titulos:novo 1 "TEXTO VISIVEL 183"))
    (pz-titulos:novo 9 "ALTERNATIVO ANTIGO")))
(defun pz-titulos:dump (/ ss i e d x f)
  (setq f (open (getenv "POSITRON_TITULOS_SAIDA") "w")
        ss (ssget "_X" '((0 . "TEXT") (8 . "2"))) i 0)
  (while (and ss (< i (sslength ss)))
    (setq e (ssname ss i) i (1+ i) d (entget e '("DiagLog"))
          x (cdr (assoc "DiagLog" (cdr (assoc -3 d)))))
    (if (and x (= (cdr (car x)) "TituloPagina"))
      (write-line (strcat "TITULO;" (itoa (cdr (cadr x))) ";texto=" (cdr (assoc 1 d))
                         ";xdata=" (cdr (caddr x))) f)))
  (write-line (strcat "LAYER;" (vl-princ-to-string (entget (tblobjname "LAYER" "2") '("Eletron")))) f)
  (close f)
  (princ))
; Rodada 184: prova independente da recriacao, sem depender do resumo do plugin.
; A fixture continua opt-in e so deve ser usada na copia feita pelo harness.
(if (= (getenv "POSITRON_CAMPOS_PROVAR") "1")
  (progn
    (setq pz-campos:antigos (ssget "_X" '((0 . "TEXT") (8 . "2"))))
    (pz-titulos:novo 8 "REV VISIVEL 184")
    (setq pz-campos:rev (entlast))
    (pz-titulos:novo 42 "CAMPO OBSOLETO 184")
    (setq pz-campos:obsoleto (entlast))
    (entmakex '((0 . "TEXT") (8 . "2") (10 950000.0 5.0 0.0) (40 . 2.5) (1 . "TEXTO COMUM 184")))
    (setq pz-campos:comum (entlast))))
(defun pz-campos:provar (/ ss i d x indice titulos rev f falhas esperado)
  (setq esperado (getenv "POSITRON_CAMPOS_TITULO_ESPERADO"))
  (if (not esperado) (setq esperado "TEXTO VISIVEL 183"))
  (setq ss (ssget "_X" '((0 . "TEXT") (8 . "2"))) i 0 titulos 0 rev 0 falhas 0)
  (while (and ss (< i (sslength ss)))
    (setq d (entget (ssname ss i) '("DiagLog")) i (1+ i)
          x (cdr (assoc "DiagLog" (cdr (assoc -3 d)))))
    (if (and x (= (cdr (car x)) "TituloPagina"))
      (progn
        (setq indice (cdr (cadr x)))
        (cond
          ((= indice 1)
            (setq titulos (1+ titulos))
            (if (/= (cdr (assoc 1 d)) esperado) (setq falhas (1+ falhas))))
          ((= indice 8)
            (setq rev (1+ rev))
            (if (or (/= (cdr (assoc 1 d)) "REV VISIVEL 184")
                    (/= (cdr (caddr x)) "REV VISIVEL 184")) (setq falhas (1+ falhas))))
          ((= indice 42) (setq falhas (1+ falhas)))))))
  (if (or (/= titulos 1) (/= rev 1) (entget pz-campos:rev) (entget pz-campos:obsoleto)
          (not (entget pz-campos:comum))) (setq falhas (1+ falhas)))
  (setq f (open (getenv "POSITRON_CAMPOS_SAIDA") "w"))
  (write-line (strcat "RESTAURA184;falhas=" (itoa falhas) ";titulo1=" (itoa titulos)
    ";rev=" (itoa rev) ";antigos-rev-obsoleto-apagados="
    (if (and (not (entget pz-campos:rev)) (not (entget pz-campos:obsoleto))) "sim" "nao")
    ";texto-comum-preservado=" (if (entget pz-campos:comum) "sim" "nao")) f)
  (close f)
  (princ))
(princ)
